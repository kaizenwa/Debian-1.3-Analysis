CMU-MIB DEFINITIONS ::= BEGIN

IMPORTS
	MODULE-IDENTITY, enterprises
	    FROM SNMPv2-SMI
	AGENT-CAPABILITIES
	    FROM SNMPv2-CONF;

cmu MODULE-IDENTITY
        LAST-UPDATED "9601120000Z"
        ORGANIZATION ""
        CONTACT-INFO "		Steve Waldbusser


				Glenn W. Waters

			Postal:	Bell-Northern Research Ltd.
				P.O. Box 3511, Station C
				Ottawa, Ontario  K1Y 4H7
				CA

			   Tel:	+1 613 763 3933

			E-mail:	gwaters@bnr.ca"
	DESCRIPTION
		"This file is provided as a running documentary on
		 the CMU v1.1b SNMP agent written by Steve Waldbusser,
		 and subsequently modified by Glenn Waters to support
		 SNMPv2's User-based Security Model."
	::= { enterprises 3 }


cmuAgents OBJECT IDENTIFIER ::= { cmu 1 }

cmuAgent AGENT-CAPABILITIES
    PRODUCT-RELEASE	"cmusnmp-1.1b-v2usec"
    STATUS		current
    DESCRIPTION		"CMU SNMP v1.1b + SNMPv2 USEC + SPARC + SunOS 4.1.1"

    SUPPORTS		SNMPv2-MIB
	INCLUDES	{ snmpGroup, snmpSetGroup, systemGroup,
		          snmpBasicNotificationsGroup,
			  snmpCommunityGroup }

    SUPPORTS		SNMPv2-USEC-MIB
	INCLUDES	{ usecBasicGroup, usecStatsGroup }

    SUPPORTS            IF-MIB
	INCLUDES	{ ifGeneralGroup, ifPacketGroup }
	VARIATION	ifLinkUpDownTrapEnable
	    ACCESS	not-implemented
	    DESCRIPTION	""
	VARIATION	ifConnectorPresent
	    ACCESS	not-implemented
	    DESCRIPTION	""
	VARIATION	ifName
	    ACCESS	not-implemented
	    DESCRIPTION	""
	VARIATION	ifHighSpeed
	    ACCESS	not-implemented
	    DESCRIPTION	""

	VARIATION	ifInMulticastPkts
	    ACCESS	not-implemented
	    DESCRIPTION	""
	VARIATION	ifInBroadcastPkts
	    ACCESS	not-implemented
	    DESCRIPTION	""
	VARIATION	ifOutMulticastPkts
	    ACCESS	not-implemented
	    DESCRIPTION	""
	VARIATION	ifOutBroadcastPkts
	    ACCESS	not-implemented
	    DESCRIPTION	""
	VARIATION	ifPromiscuousMode
	    ACCESS	not-implemented
	    DESCRIPTION	""

    SUPPORTS		IP-MIB
	INCLUDES	{ ipGroup,
			  icmpGroup }
	VARIATION	ipAdEntReasmMaxSize
	    ACCESS	not-implemented
	    DESCRIPTION	""
	VARIATION	ipNetToMediaIfIndex
	    ACCESS	not-implemented
	    DESCRIPTION	""
	VARIATION	ipNetToMediaPhysAddress
	    ACCESS	not-implemented
	    DESCRIPTION	""
	VARIATION	ipNetToMediaNetAddress
	    ACCESS	not-implemented
	    DESCRIPTION	""
	VARIATION	ipNetToMediaType
	    ACCESS	not-implemented
	    DESCRIPTION	""
	VARIATION	ipRoutingDiscards
	    ACCESS	not-implemented
	    DESCRIPTION	""

    SUPPORTS		TCP-MIB
	INCLUDES	{ tcpGroup }
	VARIATION	tcpInErrs
	    ACCESS	not-implemented
	    DESCRIPTION	""
	VARIATION	tcpOutRsts
	    ACCESS	not-implemented
	    DESCRIPTION	""

    SUPPORTS		UDP-MIB
	INCLUDES	{ udpGroup }
	VARIATION	udpLocalAddress
	    ACCESS	not-implemented
	    DESCRIPTION	""
	VARIATION	udpLocalPort
	    ACCESS	not-implemented
	    DESCRIPTION	""

    ::= { cmuAgents 1 }


END
