MAU-MIB DEFINITIONS ::= BEGIN

        IMPORTS
            Counter                             FROM RFC1155-SMI
            OBJECT-TYPE                         FROM RFC-1212
            TRAP-TYPE                           FROM RFC-1215;

        snmpDot3MauMgt OBJECT IDENTIFIER ::= { mib-2 26 }

        --                      References
        --
        -- The following references are used throughout this MIB:
        --
        -- [RFC 1213]
        --    refers to McCloghrie, K., and M. Rose, Editors,
        --    Management Information Base for Network Management
        --    of TCP/IP-based internets: MIB-II, STD 17, RFC 1213,
        --    Hughes LAN Systems, Performance Systems International,
        --    March 1991.
        --
        -- [RFC 1368]
        --    refers to McMaster, D.,  and K. McCloghrie, Editors,
        --    Definitions of Managed Objects for IEEE 802.3 Repeater
        --    Devices, RFC 1368, SynOptics Communications, Hughes
        --    LAN Systems, October 1992.
        --
        -- [IEEE 802.3 MAU Mgt]
        --    refers to IEEE P802.3p, 'Layer Management for 10 Mb/s
        --    Medium Access Unit (MAUs), Section 20,' Draft Supplement
        --    to ANSI/IEEE 802.3, Draft 5, 11 July 1992.

        --                      MIB Groups
        --
        --   The dot3RpMauBasicGroup is mandatory for MAUs attached to
        --     repeaters.
        --   The dot3IfMauBasicGroup is mandatory for MAUs attached to
        --     DTEs (interfaces).
        --   The dot3BroadMauBasicGroup is mandatory for broadband MAUs
        --     attached to DTEs.

        dot3RpMauBasicGroup


            OBJECT IDENTIFIER ::= { snmpDot3MauMgt 1 }
        dot3IfMauBasicGroup
            OBJECT IDENTIFIER ::= { snmpDot3MauMgt 2 }
        dot3BroadMauBasicGroup
            OBJECT IDENTIFIER ::= { snmpDot3MauMgt 3 }

        -- object identifiers for MAU types
        --  (see rpMauType and ifMauType for usage)
        dot3MauType
            OBJECT IDENTIFIER ::= { snmpDot3MauMgt 4 }
        dot3MauTypeAUI        -- no internal MAU, view from AUI
            OBJECT IDENTIFIER ::= { dot3MauType 1 }
        dot3MauType10Base5    -- thick coax MAU (per 802.3 section 8)
            OBJECT IDENTIFIER ::= { dot3MauType 2 }
        dot3MauTypeFoirl      -- FOIRL MAU (per 802.3 section 9.9)
            OBJECT IDENTIFIER ::= { dot3MauType 3 }
        dot3MauType10Base2    -- thin coax MAU (per 802.3 section 10)
            OBJECT IDENTIFIER ::= { dot3MauType 4 }
        dot3MauType10BaseT    -- UTP MAU (per 802.3 section 14)
            OBJECT IDENTIFIER ::= { dot3MauType 5 }
        dot3MauType10BaseFP   -- passive fiber MAU (per 802.3 section 16)
            OBJECT IDENTIFIER ::= { dot3MauType 6 }
        dot3MauType10BaseFB   -- sync fiber MAU (per 802.3 section 17)
            OBJECT IDENTIFIER ::= { dot3MauType 7 }
        dot3MauType10BaseFL   -- async fiber MAU (per 802.3 section 18)
            OBJECT IDENTIFIER ::= { dot3MauType 8 }
        dot3MauType10Broad36  -- broadband DTE MAU (per 802.3 section 11)
            -- note that 10BROAD36 MAUs can be attached to interfaces but
            -- not to repeaters
            OBJECT IDENTIFIER ::= { dot3MauType 9 }

        --
        --                    The Repeater MAU Basic Group
        --
        -- Implementation of the Repeater MAU Basic Group is mandatory
        -- for MAUs attached to repeaters.

        --
        -- The Basic Repeater MAU Table
        --

        rpMauTable OBJECT-TYPE
            SYNTAX    SEQUENCE OF RpMauEntry
            ACCESS    not-accessible
            STATUS    mandatory
            DESCRIPTION


                    "Table of descriptive and status information about
                    the MAU(s) attached to the ports of a repeater."
            ::= { dot3RpMauBasicGroup 1 }

        rpMauEntry OBJECT-TYPE
            SYNTAX    RpMauEntry
            ACCESS    not-accessible
            STATUS    mandatory
            DESCRIPTION
                    "An entry in the table, containing information
                    about a single MAU."
            INDEX    { rpMauGroupIndex, rpMauPortIndex, rpMauIndex }
            ::= { rpMauTable 1 }

        RpMauEntry ::=
            SEQUENCE {
                rpMauGroupIndex
                    INTEGER,
                rpMauPortIndex
                    INTEGER,
                rpMauIndex
                    INTEGER,
                rpMauType
                    OBJECT IDENTIFIER,
                rpMauStatus
                    INTEGER,
                rpMauMediaAvailable
                    INTEGER,
                rpMauMediaAvailableStateExits
                    Counter,
                rpMauJabberState
                    INTEGER,
                rpMauJabberingStateEnters
                    Counter
            }

        rpMauGroupIndex OBJECT-TYPE
            SYNTAX    INTEGER (1..1024)
            ACCESS    read-only
            STATUS    mandatory
            DESCRIPTION
                    "This variable uniquely identifies the repeater
                    group containing the port to which the MAU
                    described by this entry is connected."
            REFERENCE
                    "Reference RFC1368, rptrGroupIndex."
            ::= { rpMauEntry 1 }


        rpMauPortIndex OBJECT-TYPE
            SYNTAX    INTEGER (1..1024)
            ACCESS    read-only
            STATUS    mandatory
            DESCRIPTION
                    "This variable uniquely identifies the repeater
                    port within group rpMauGroupIndex to which the MAU
                    described by this entry is connected."
            REFERENCE
                    "Reference RFC 1368, rptrPortIndex."
            ::= { rpMauEntry 2 }

        rpMauIndex OBJECT-TYPE
            SYNTAX    INTEGER (1..9)
            ACCESS    read-only
            STATUS    mandatory
            DESCRIPTION
                    "This variable uniquely identifies the MAU
                    connected to port rpMauPortIndex within group
                    rpMauGroupIndex that is described by this entry."
            REFERENCE
                    "Reference IEEE 802.3 MAU Mgt, 20.2.3.2, aMAUID."
            ::= { rpMauEntry 3 }

        rpMauType OBJECT-TYPE
            SYNTAX    OBJECT IDENTIFIER
            ACCESS    read-only
            STATUS    mandatory
            DESCRIPTION
                    "This object identifies the 10 Mb/s baseband MAU
                    type.  An initial set of MAU types are defined
                    above.  The assignment of OBJECT IDENTIFIERs to
                    new types of MAUs is managed by the IANA.  If the
                    MAU type is unknown, the object identifier

                        unknownMauType OBJECT IDENTIFIER ::= { 0 0 }

                    is returned.  Note that unknownMauType is a
                    syntactically valid object identifier, and any
                    conformant implementation of ASN.1 and the BER
                    must be able to generate and recognize this
                    value."
            REFERENCE
                    "Reference IEEE 802.3 MAU Mgt, 20.2.3.2,
                    aMAUType."
            ::= { rpMauEntry 4 }

        rpMauStatus OBJECT-TYPE


            SYNTAX    INTEGER {
                          other(1),
                          unknown(2),
                          operational(3),
                          standby(4),
                          shutdown(5),
                          reset(6)
                      }
            ACCESS    read-write
            STATUS    mandatory
            DESCRIPTION
                    "The current state of the MAU.  This object may be
                    implemented as a read-only object by those agents
                    and MAUs that do not implement software control of
                    the MAU state.  Some agents may not support
                    setting the value of this object to some of the
                    enumerated values.

                    The value other(1) is returned if the MAU is in a
                    state other than one of the states 2 through 6.

                    The value unknown(2) is returned when the MAU's
                    true state is unknown; for example, when it is
                    being initialized.

                    A MAU in the operational(3) state is fully
                    functional, operates, and passes signals to its
                    attached DTE or repeater port in accordance to its
                    specification.

                    A MAU in standby(4) state forces DI and CI and the
                    media transmitter to idle.  Standby(4) mode only
                    applies to link type MAUs.  The state of
                    rpMauMediaAvailable is unaffected.

                    A MAU in shutdown(5) state assumes the same
                    condition on DI, CI, and the media transmitter as
                    though it were powered down.  The MAU may return
                    other(1) value for the mauJabber and
                    rpMauMediaAvailable objects when it is in this
                    state.  For an AUI, this state will remove power
                    from the AUI.

                    Setting this variable to the value reset(6) resets
                    the MAU in the same manner as a power-off, power-
                    on cycle of at least one-half second would.  The
                    agent is not required to return the value reset
                    (6).


                    Setting this variable to the value operational(3),
                    standby(4), or shutdown(5) causes the MAU to
                    assume the respective state except that setting a
                    mixing-type MAU or an AUI to standby(4) will cause
                    the MAU to enter the shutdown state."
                REFERENCE
                    "Reference IEEE 802.3 MAU Mgt, 20.2.3.2,
                    aMAUAdminState, and 20.2.3.3, acMAUAdminControl
                    and acResetMAUAction."
            ::= { rpMauEntry 5 }

        rpMauMediaAvailable OBJECT-TYPE
            SYNTAX    INTEGER {
                          other(1),
                          unknown(2),
                          available(3),
                          notAvailable(4),
                          remoteFault(5),
                          invalidSignal(6)
                      }
            ACCESS    read-only
            STATUS    mandatory
            DESCRIPTION
                    "If the MAU is a link or fiber type (FOIRL,
                    10BASE-T, 10BASE-F) then this is equivalent to the
                    link test fail state/low light function.  For an
                    AUI or a coax (including broadband) MAU this
                    indicates whether or not loopback is detected on
                    the DI circuit.  The value of this attribute
                    persists between packets for MAU types AUI,
                    10BASE5, 10BASE2, 10BROAD36, and 10BASE-FP.

                    The value other(1) is returned if the
                    mediaAvailable state is not one of 2 through 6.

                    The value unknown(2) is returned when the MAU's
                    true state is unknown; for example, when it is
                    being initialized.  At power-up or following a
                    reset, the value of this attribute will be unknown
                    for AUI, coax, and 10BASE-FP MAUs.  For these MAUs
                    loopback will be tested on each transmission
                    during which no collision is detected.  If DI is
                    receiving input when DO returns to IDL after a
                    transmission and there has been no collision
                    during the transmission then loopback will be
                    detected.  The value of this attribute will only
                    change during non-collided transmissions for AUI,
                    coax, and 10BASE-FP MAUs.


                    The value available(3) indicates that the link,
                    light, or loopback is normal.  The value
                    notAvailable(4) indicates link loss, low light, or
                    no loopback.

                    The value remoteFault(5) indicates that a fault
                    has been detected at the remote end of the link.
                    The value invalidSignal(6) indicates that an
                    invalid signal has been received from the other
                    end of the link.  Both remoteFault(5) and
                    invalidSignal(6) apply only to MAUs of type
                    10BASE-FB."
            REFERENCE
                    "Reference IEEE 802.3 MAU Mgt, 20.2.3.2,
                    aMediaAvailable."
            ::= { rpMauEntry 6 }

        rpMauMediaAvailableStateExits OBJECT-TYPE
            SYNTAX    Counter
            ACCESS    read-only
            STATUS    mandatory
            DESCRIPTION
                    "A count of the number of times that
                    rpMauMediaAvailable for this MAU instance leaves
                    the state available(3)."
            REFERENCE
                    "Reference IEEE 802.3 MAU Mgt, 20.2.3.2,
                    lostMediaCount."
            ::= { rpMauEntry 7 }

        rpMauJabberState OBJECT-TYPE
            SYNTAX    INTEGER {
                          other(1),
                          unknown(2),
                          noJabber(3),
                          jabbering(4)
                      }
            ACCESS    read-only
            STATUS    mandatory
            DESCRIPTION
                    "The value other(1) is returned if the jabber
                    state is not 2, 3, or 4.  The agent must always
                    return other(1) for MAU type dot3MauTypeAUI.

                    The value unknown(2) is returned when the MAU's
                    true state is unknown; for example, when it is
                    being initialized.


                    If the MAU is not jabbering the agent returns
                    noJabber(3).  This is the 'normal' state.

                    If the MAU is in jabber state the agent returns
                    the jabbering(4) value."
            REFERENCE
                    "Reference IEEE 802.3 MAU Mgt, 20.2.3.2,
                    aJabber.jabberFlag."
            ::= { rpMauEntry 8 }

        rpMauJabberingStateEnters OBJECT-TYPE
            SYNTAX    Counter
            ACCESS    read-only
            STATUS    mandatory
            DESCRIPTION
                    "A count of the number of times that
                    rpMauJabberState for this MAU instance enters the
                    state jabbering(4).  For a MAU of type
                    dot3MauTypeAUI, this counter will always indicate
                    zero."
            REFERENCE
                    "Reference IEEE 802.3 MAU Mgt, 20.2.3.2,
                    aJabber.jabberCounter."
            ::= { rpMauEntry 9 }

        --
        --                    The Interface MAU Basic Group
        --
        -- Implementation of the Interface MAU Basic Group is mandatory
        -- for MAUs attached to DTEs (interfaces).

        --
        -- The Basic Interface MAU Table
        --

        ifMauTable OBJECT-TYPE
            SYNTAX    SEQUENCE OF IfMauEntry
            ACCESS    not-accessible
            STATUS    mandatory
            DESCRIPTION
                    "Table of descriptive and status information about
                    the MAU(s) attached to an interface."
            ::= { dot3IfMauBasicGroup 1 }

        ifMauEntry OBJECT-TYPE
            SYNTAX    IfMauEntry
            ACCESS    not-accessible


            STATUS    mandatory
            DESCRIPTION
                    "An entry in the table, containing information
                    about a single MAU."
            INDEX    { ifMauIfIndex, ifMauIndex }
            ::= { ifMauTable 1 }

        IfMauEntry ::=
            SEQUENCE {
                ifMauIfIndex
                    INTEGER,
                ifMauIndex
                    INTEGER,
                ifMauType
                    OBJECT IDENTIFIER,
                ifMauStatus
                    INTEGER,
                ifMauMediaAvailable
                    INTEGER,
                ifMauMediaAvailableStateExits
                    Counter,
                ifMauJabberState
                    INTEGER,
                ifMauJabberingStateEnters
                    Counter
            }

        ifMauIfIndex OBJECT-TYPE
            SYNTAX    INTEGER
            ACCESS    read-only
            STATUS    mandatory
            DESCRIPTION
                    "This variable uniquely identifies the interface
                    to which the MAU described by this entry is
                    connected."
            REFERENCE
                    "Reference RFC 1213, ifIndex."
            ::= { ifMauEntry 1 }

        ifMauIndex OBJECT-TYPE
            SYNTAX    INTEGER (1..9)
            ACCESS    read-only
            STATUS    mandatory
            DESCRIPTION
                    "This variable uniquely identifies the MAU
                    connected to interface ifMauIfIndex that is
                    described by this entry."
            REFERENCE


                    "Reference IEEE 802.3 MAU Mgt, 20.2.3.2, aMAUID."
            ::= { ifMauEntry 2 }

        ifMauType OBJECT-TYPE
            SYNTAX    OBJECT IDENTIFIER
            ACCESS    read-only
            STATUS    mandatory
            DESCRIPTION
                    "This object identifies the 10 Mb/s baseband or
                    broadband MAU type.  An initial set of MAU types
                    are defined above.  The assignment of OBJECT
                    IDENTIFIERs to new types of MAUs is managed by the
                    IANA.  If the MAU type is unknown, the object
                    identifier

                        unknownMauType OBJECT IDENTIFIER ::= { 0 0 }

                    is returned.  Note that unknownMauType is a
                    syntactically valid object identifier, and any
                    conformant implementation of ASN.1 and the BER
                    must be able to generate and recognize this
                    value."
            REFERENCE
                    "Reference IEEE 802.3 MAU Mgt, 20.2.3.2,
                    aMAUType."
            ::= { ifMauEntry 3 }

        ifMauStatus OBJECT-TYPE
            SYNTAX    INTEGER {
                          other(1),
                          unknown(2),
                          operational(3),
                          standby(4),
                          shutdown(5),
                          reset(6)
                      }
            ACCESS    read-write
            STATUS    mandatory
            DESCRIPTION
                    "The current state of the MAU.  This object may be
                    implemented as a read-only object by those agents
                    and MAUs that do not implement software control of
                    the MAU state.  Some agents may not support
                    setting the value of this object to some of the
                    enumerated values.

                    The value other(1) is returned if the MAU is in a
                    state other than one of the states 2 through 6.


                    The value unknown(2) is returned when the MAU's
                    true state is unknown; for example, when it is
                    being initialized.

                    A MAU in the operational(3) state is fully
                    functional, operates, and passes signals to its
                    attached DTE or repeater port in accordance to its
                    specification.

                    A MAU in standby(4) state forces DI and CI and the
                    media transmitter to idle.  Standby(4) mode only
                    applies to link type MAUs.  The state of
                    ifMauMediaAvailable is unaffected.

                    A MAU in shutdown(5) state assumes the same
                    condition on DI, CI, and the media transmitter as
                    though it were powered down.  The MAU may return
                    other(1) value for the mauJabber and
                    ifMauMediaAvailable objects when it is in this
                    state.  For an AUI, this state will remove power
                    from the AUI.

                    Setting this variable to the value reset(6) resets
                    the MAU in the same manner as a power-off, power-
                    on cycle of at least one-half second would.  The
                    agent is not required to return the value reset
                    (6).

                    Setting this variable to the value operational(3),
                    standby(4), or shutdown(5) causes the MAU to
                    assume the respective state except that setting a
                    mixing-type MAU or an AUI to standby(4) will cause
                    the MAU to enter the shutdown state."
                REFERENCE
                    "Reference IEEE 802.3 MAU Mgt, 20.2.3.2,
                    aMAUAdminState, and 20.2.3.3, acMAUAdminControl
                    and acResetMAUAction."
            ::= { ifMauEntry 4 }

        ifMauMediaAvailable OBJECT-TYPE
            SYNTAX    INTEGER {
                          other(1),
                          unknown(2),
                          available(3),
                          notAvailable(4),
                          remoteFault(5),
                          invalidSignal(6)
                      }


            ACCESS    read-only
            STATUS    mandatory
            DESCRIPTION
                    "If the MAU is a link or fiber type (FOIRL,
                    10BASE-T, 10BASE-F) then this is equivalent to the
                    link test fail state/low light function.  For an
                    AUI or a coax (including broadband) MAU this
                    indicates whether or not loopback is detected on
                    the DI circuit.  The value of this attribute
                    persists between packets for MAU types AUI,
                    10BASE5, 10BASE2, 10BROAD36, and 10BASE-FP.

                    The value other(1) is returned if the
                    mediaAvailable state is not one of 2 through 6.

                    The value unknown(2) is returned when the MAU's
                    true state is unknown; for example, when it is
                    being initialized.  At power-up or following a
                    reset, the value of this attribute will be unknown
                    for AUI, coax, and 10BASE-FP MAUs.  For these MAUs
                    loopback will be tested on each transmission
                    during which no collision is detected.  If DI is
                    receiving input when DO returns to IDL after a
                    transmission and there has been no collision
                    during the transmission then loopback will be
                    detected.  The value of this attribute will only
                    change during non-collided transmissions for AUI,
                    coax, and 10BASE-FP MAUs.

                    The value available(3) indicates that the link,
                    light, or loopback is normal.  The value
                    notAvailable(4) indicates link loss, low light, or
                    no loopback.

                    The value remoteFault(5) indicates that a fault
                    has been detected at the remote end of the link.
                    The value invalidSignal(6) indicates that an
                    invalid signal has been received from the other
                    end of the link.  Both remoteFault(5) and
                    invalidSignal(6) apply only to MAUs of type
                    10BASE-FB."
            REFERENCE
                    "Reference IEEE 802.3 MAU Mgt, 20.2.3.2,
                    aMediaAvailable."
            ::= { ifMauEntry 5 }

        ifMauMediaAvailableStateExits OBJECT-TYPE
            SYNTAX    Counter


            ACCESS    read-only
            STATUS    mandatory
            DESCRIPTION
                    "A count of the number of times that
                    ifMauMediaAvailable for this MAU instance leaves
                    the state available(3)."
            REFERENCE
                    "Reference IEEE 802.3 MAU Mgt, 20.2.3.2,
                    lostMediaCount."
            ::= { ifMauEntry 6 }

        ifMauJabberState OBJECT-TYPE
            SYNTAX    INTEGER {
                          other(1),
                          unknown(2),
                          noJabber(3),
                          jabbering(4)
                      }
            ACCESS    read-only
            STATUS    mandatory
            DESCRIPTION
                    "The value other(1) is returned if the jabber
                    state is not 2, 3, or 4.  The agent must always
                    return other(1) for MAU type dot3MauTypeAUI.

                    The value unknown(2) is returned when the MAU's
                    true state is unknown; for example, when it is
                    being initialized.

                    If the MAU is not jabbering the agent returns
                    noJabber(3).  This is the 'normal' state.

                    If the MAU is in jabber state the agent returns
                    the jabbering(4) value."
            REFERENCE
                    "Reference IEEE 802.3 MAU Mgt, 20.2.3.2,
                    aJabber.jabberFlag."
            ::= { ifMauEntry 7 }

        ifMauJabberingStateEnters OBJECT-TYPE
            SYNTAX    Counter
            ACCESS    read-only
            STATUS    mandatory
            DESCRIPTION
                    "A count of the number of times that
                    ifMauJabberState for this MAU instance enters the
                    state jabbering(4).  For a MAU of type
                    dot3MauTypeAUI, this counter will always indicate


                    zero."
            REFERENCE
                    "Reference IEEE 802.3 MAU Mgt, 20.2.3.2,
                    aJabber.jabberCounter."
            ::= { ifMauEntry 8 }

        --
        --                    The Broadband MAU Basic Group
        --
        -- Implementation of the Broadband MAU Basic Group is mandatory
        -- for broadband MAUs attached to DTEs.

        --
        -- The Basic Broadband MAU Table
        --

        broadMauBasicTable OBJECT-TYPE
            SYNTAX    SEQUENCE OF BroadMauBasicEntry
            ACCESS    not-accessible
            STATUS    mandatory
            DESCRIPTION
                    "Table of descriptive and status information about
                    the broadband MAUs connected to interfaces."
            ::= { dot3BroadMauBasicGroup 1 }

        broadMauBasicEntry OBJECT-TYPE
            SYNTAX    BroadMauBasicEntry
            ACCESS    not-accessible
            STATUS    mandatory
            DESCRIPTION
                    "An entry in the table, containing information
                    about a single broadband MAU."
            INDEX    { broadMauIfIndex, broadMauIndex }
            ::= { broadMauBasicTable 1 }

        BroadMauBasicEntry ::=
            SEQUENCE {
                broadMauIfIndex
                    INTEGER,
                broadMauIndex
                    INTEGER,
                broadMauXmtRcvSplitType
                    INTEGER,
                broadMauXmtCarrierFreq
                    INTEGER,
                broadMauTranslationFreq
                    INTEGER


            }

        broadMauIfIndex OBJECT-TYPE
            SYNTAX    INTEGER
            ACCESS    read-only
            STATUS    mandatory
            DESCRIPTION
                    "This variable uniquely identifies the interface
                    to which the MAU described by this entry is
                    connected."
            REFERENCE
                    "Reference RFC 1213, ifIndex."
            ::= { broadMauBasicEntry 1 }

        broadMauIndex OBJECT-TYPE
            SYNTAX    INTEGER (1..9)
            ACCESS    read-only
            STATUS    mandatory
            DESCRIPTION
                    "This variable uniquely identifies the MAU
                    connected to interface broadMauIfIndex that is
                    described by this entry."
            REFERENCE
                    "Reference IEEE 802.3 MAU Mgt, 20.2.3.2, aMAUID."
            ::= { broadMauBasicEntry 2 }

        broadMauXmtRcvSplitType OBJECT-TYPE
            SYNTAX    INTEGER {
                          other(1),
                          single(2),
                          dual(3)
                      }
            ACCESS    read-only
            STATUS    mandatory
            DESCRIPTION
                    "This object indicates the type of frequency
                    multiplexing/cabling system used to separate the
                    transmit and receive paths for the 10BROAD36 MAU.

                    The value other(1) is returned if the split type
                    is not either single or dual.

                    The value single(2) indicates a single cable
                    system.  The value dual(3) indicates a dual cable
                    system, offset normally zero."
            REFERENCE
                    "Reference IEEE 802.3 MAU Mgt, 20.2.3.2,
                    aBbMAUXmitRcvSplitType."


            ::= { broadMauBasicEntry 3 }

        broadMauXmtCarrierFreq OBJECT-TYPE
            SYNTAX    INTEGER
            ACCESS    read-only
            STATUS    mandatory
            DESCRIPTION
                    "This variable indicates the transmit carrier
                    frequency of the 10BROAD36 MAU in MHz/4; that is,
                    in units of 250 kHz."
            REFERENCE
                    "Reference IEEE 802.3 MAU Mgt, 20.2.3.2,
                    aBroadbandFrequencies.xmitCarrierFrequency."
            ::= { broadMauBasicEntry 4 }

        broadMauTranslationFreq OBJECT-TYPE
            SYNTAX    INTEGER
            ACCESS    read-only
            STATUS    mandatory
            DESCRIPTION
                    "This variable indicates the translation offset
                    frequency of the 10BROAD36 MAU in MHz/4; that is,
                    in units of 250 kHz."
            REFERENCE
                    "Reference IEEE 802.3 MAU Mgt, 20.2.3.2,
                    aBroadbandFrequencies.translationFrequency."
            ::= { broadMauBasicEntry 5 }

        -- Traps for use by 802.3 MAUs

        -- Traps are defined using the conventions in RFC 1215 [8].

        rpMauJabberTrap TRAP-TYPE
            ENTERPRISE  snmpDot3MauMgt
            VARIABLES   { rpMauJabberState }
            DESCRIPTION
                    "This trap is sent whenever a managed repeater MAU
                    enters the jabber state.

                    The agent must throttle the generation of
                    consecutive rpMauJabberTraps so that there is at
                    least a five-second gap between them."
            REFERENCE
                    "Reference IEEE 802.3 MAU Mgt, 20.2.3.4,
                    nJabberNotification."
            ::= 1


        ifMauJabberTrap TRAP-TYPE
            ENTERPRISE  snmpDot3MauMgt
            VARIABLES   { ifMauJabberState }
            DESCRIPTION
                    "This trap is sent whenever a managed interface
                    MAU enters the jabber state.

                    The agent must throttle the generation of
                    consecutive ifMauJabberTraps so that there is at
                    least a five-second gap between them."
            REFERENCE
                    "Reference IEEE 802.3 MAU Mgt, 20.2.3.4,
                    nJabberNotification."
            ::= 2

END
